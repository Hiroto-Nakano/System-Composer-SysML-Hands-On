# SysMLArchModel_REQ
Copyright 2022 - 2022 The MathWorks, Inc

## 1: Total Mass (Functional)
総重量はxxx kg以下であること

## 2: Total Volume (Functional)
体積はxxx mm^3以下であること

## 3: Response (Functional)
アクセルペダルの踏み込み率に対して0→100%のステップ入力がされた際に、制御対象であるスロットル角度センサ信号(0～5 V)がステップ入力のステップ時間を起点とし、100 ms以内に目標値の定常偏差±10 %未満に収束すること

### #8: Monotonic Response (Functional)
応答開始後、PositionSensorVoltage のそれまでの最大値からの低下量が0.10V以下であること。

## 4: Stability (Functional)
ゲイン余裕はxx dB以上とし、位相余裕はxx deg以上を確保すること

## 5: Plant Parameters (Functional)
制御対象のスロットルボディはコンポーネントに割り当てたパラメータ値 に基づいてモデリングすること

## 6: Sensor Voltage (Functional)
センサ電圧の基準値は5 Vとすること

## 7: Motor Driver DC Voltage (Functional)
スロットルボディ内のスロットル角度を動かすモータに対するモータドライバに入力するDC電圧は12 Vとすること
